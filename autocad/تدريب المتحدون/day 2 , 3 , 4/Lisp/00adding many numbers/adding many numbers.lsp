(defun c:adona ()
(setq eseto  (ssget ))
(setq cntro 0)
(setq dlisto nil)
(while (< cntro (sslength eseto))
(setq eno (ssname eseto cntro))
(setq enlisto (entget eno ))
(setq baba (atof (cdr ( assoc 1 enlisto))))
(setq dlisto (append dlisto (list baba)))
(setq cntro (+ 1 cntro))
)
(setq ro (apply '+ dlisto))
(setvar "osmode" 15359)
(setq point1 (getpoint "\nPick point"))
(setvar "osmode" 0)
(setq point2 (mapcar '+ point1 (list 0.5 0.15)))
(command "layer" "m" "ali_text" "")
(command "text" "j" "mc" point2 "0.25" "0" (rtos ro 2 2) "")
(setvar "osmode" 15359)	
)
